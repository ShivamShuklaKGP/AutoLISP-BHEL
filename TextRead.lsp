(defun rect( n list1)
(setq x1 (nth n list1));(getreal "\n Give the x coordinate of the point:"))
(setq n (+ n 1 ))
(setq y1 (nth n list1));(getreal "\n Give the y coordinate of the point:"))
(setq n (+ n 1 ))
(setq pt1 (list x1 y1 0.0))
(setq length1 (nth n list1));(getreal "\n Give the length of the rectangle:"))
(setq n (+ n 1 ))
(setq width1 (nth n list1));(getreal "\n Give the width of the rectangle:"))
(setq n (+ n 1 ))
(setq pt2 (polar pt1 0 length1))
(setq pt3 (polar pt2 (/ pi 2) width1))
(setq pt4 (polar pt3 pi length1))
(setq flag (nth n list1));(getint "\n Do you want to extrude it (1 for yes 0 for No):"))
(setq n (+ n 1 ))
(setq z1 0.0 z2 0.0 deltah 0.0)
(if (= flag 1)
(progn
(setq z1 (nth n list1));(getreal "\n Give the height from which you want to begin:"))
(setq n (+ n 1 ))
(setq z2 (nth n list1));(getreal "\n Give the height at which you want to stop:"))
(setq n (+ n 1 ))
(setq deltah (nth n list1)); (getreal "\n Give the height differential required:"))
(setq n (+ n 1))
(setq pt1 (list x1 y1 z1))
(setq pt2 (polar pt1 0 length1))
(setq pt3 (polar pt2 (/ pi 2) width1))
(setq pt4 (polar pt3 pi length1))
  (while (< z1 z2)
   (command "line" pt1 pt2 pt3 pt4 pt1 "")
   (setq z1 (+ z1 deltah))
   (setq pt1 (list x1 y1 z1))
   (setq pt2 (polar pt1 0 length1))
   (setq pt3 (polar pt2 (/ pi 2) width1))
   (setq pt4 (polar pt3 pi length1))))
 (progn
(command "line" pt1 pt2 pt3 pt4 pt1 "")))
(setq height1 (nth n list1));(getreal "\nFont in coordinate units for tag:"))
(setq n (+ n 1 ))
;(setq heightstr(strcat "" (rtos height1) ""))
;(prompt "\nEnter the tag text:")
;(setq tagtext (strcat (read-line) ""))
;(command "text" (list (+ x1 length1) (+ y1 width1) 0) heightstr 45.0 tagtext)
)              ; Function to make rectangle from a single points' coordinates - options include extrude or not extrude and has tagging ability



(defun quadi( n list1) ; Function can make any quadilateral has options of extrusion and has tagging ability
(setq x1 (nth n list1));(getreal "\n Give the x coordinate of the first point:"))
(setq n (+ n 1))
(setq y1 (nth n list1));(getreal "\n Give the y coordinate of the first point:"))
(setq n (+ n 1))
(setq pt1 (list x1 y1 0.0))
(setq x2 (nth n list1));(getreal "\n Give the x coordinate of the second point:"))
(setq n (+ n 1))
(setq y2 (nth n list1));(getreal "\n Give the y coordinate of the second point:"))
(setq n (+ n 1))
(setq pt2 (list x2 y2 0.0))
(setq x3 (nth n list1));(getreal "\n Give the x coordinate of the third point:"))
(setq n (+ n 1))
(setq y3 (nth n list1));(getreal "\n Give the y coordinate of the third point:"))
(setq n (+ n 1))
(setq pt3 (list x3 y3 0.0))
(setq x4 (nth n list1));(getreal "\n Give the x coordinate of the fourth point:"))
(setq n (+ n 1))
(setq y4 (nth n list1));(getreal "\n Give the y coordinate of the fourth point:"))
(setq n (+ n 1))
(setq pt4 (list x4 y4 0.0))
(setq flag (nth n list1));(getint "\n Do you want to extrude it (1 for yes 0 for No):"))
(setq n (+ n 1))
(setq z1 0.0 z2 0.0 deltah 0.0)
(if (= flag 1)
 (progn
 (setq z1 (nth n list1));(getreal "\n Give the height from which you want to begin:"))
 (setq n (+ n 1))
 (setq z2 (nth n list1));(getreal "\n Give the height at which you want to stop:"))
 (setq n (+ n 1))
 (setq deltah (nth n list1));(getreal "\n Give the height differential required:"))
 (setq n (+ n 1))
 (setq pt2 (list x2 y2 z1))
 (setq pt3 (list x3 y3 z1))
 (setq pt4 (list x4 y4 z1))
 (setq pt1 (list x1 y1 z1))
  (while (< z1 z2)
   (command "line" pt1 pt2 pt3 pt4 pt1 "")
   (setq z1 (+ z1 deltah))
   (setq pt2 (list x2 y2 z1))
   (setq pt3 (list x3 y3 z1))
   (setq pt4 (list x4 y4 z1))
   (setq pt1 (list x1 y1 z1))))
   (progn)
   )
 (if (= flag 0 )
  (command "line" pt1 pt2 pt3 pt4 pt1 ""))
 (setq flag2 (nth n list1));(getint "\n Do you want a hut above it(1 for Yes and 0 for No):"))
 (setq n (+ n 1))
 (if (= flag2 1)
 (progn
  (setq xav (/ (+ x1 x2 x3 x4) 4))
  (setq yav (/ (+ y1 y2 y3 y4) 4))
  (setq x11 x1)
  (setq x22 x2)
  (setq x33 x3)
  (setq x44 x4)
  (setq y44 y4)
  (setq y33 y3)
  (setq y22 y2)
  (setq y11 y1)
  (while (< z1 (+ z2 30))
   (setq z1 (+ z1 1))
   (command "line" pt1 pt2 pt3 pt4 pt1 "")
   (setq x11 (+ x11 (/ (- xav x1) 30)))
   (setq x22 (+ x22 (/ (- xav x2) 30)))
   (setq x33 (+ x33 (/ (- xav x3) 30)))
   (setq x44 (+ x44 (/ (- xav x4) 30)))
   (setq y11 (+ y11 (/ (- yav y1) 30)))
   (setq y22 (+ y22 (/ (- yav y2) 30)))
   (setq y33 (+ y33 (/ (- yav y3) 30)))
   (setq y44 (+ y44 (/ (- yav y4) 30)))
   (setq pt2 (list x22 y22 z1))
   (setq pt3 (list x33 y33 z1))
   (setq pt4 (list x44 y44 z1))
   (setq pt1 (list x11 y11 z1)))))
   (progn)
   (setq height1 (nth n list1));(getreal "\nFont in coordinate units for tag:"))
   (setq n (+ n 1))
   ;(setq heightstr (strcat "" (rtos height1) ""))
   ;(prompt "\nEnter the tag text:")
   ;(setq tagtext (strcat (read-line) ""))
   ;(command "text" (list (max x1 x2 x3 x4) (max y1 y2 y3 y4) 0) heightstr 45.0 tagtext)
   )

(defun cyl(n list1)   ;Function to make a cylinder given its centers coordinates, height differential, and Z coordinates of start and end
(setq x1 (nth n list1));(getreal "\n Give the X coordinate of the Center:"))
(setq n (+ n 1))
(setq y1 (nth n list1));(getreal "\n Give the Y coordinate of the Center:"))
(setq n (+ n 1))
(setq z1 (nth n list1));(getreal "\n Give the Z Coordinate from where to begin:"))
(setq n (+ n 1))
(setq z2 (nth n list1));(getreal "\n Give the Z Coordinate upto which Cylinder has to be made:"))
(setq n (+ n 1))
(setq rad (nth n list1));(getreal "\n Give the radius:"))
(setq n (+ n 1))
(setq radstr (strcat (rtos rad) ""))
(setq deltah (nth n list1));(getreal "\n Give the height differential:"))
(setq n (+ n 1))
(while (< z1 z2)
(setq ctr (list x1 y1 z1))
(command "circle" ctr radstr)
(setq z1 (+ z1 deltah))
)
   (setq height1 (nth n list1));(getreal "\nFont in coordinate units for tag:"))
   (setq n (+ n 1))
   ;(setq heightstr (strcat "" (rtos height1) ""))
   ;(prompt "\nEnter the tag text:")
   ;(setq tagtext (strcat (read-line) ""))
   ;(command "text" (list (+ x1 rad ) y1 0) heightstr 45.0 tagtext)
)

(defun cone(n list1) ; Function that enables one to make Cones using different Options
(setq x1 (nth n list1));(getreal "\n Give the X coordinate of the Center:"))
(setq n (+ n 1))
(setq y1 (nth n list1));(getreal "\n Give the Y coordinate of the Center:"))
(setq n (+ n 1))
(setq z1 (nth n list1));(getreal "\n Give the Z Coordinate from where to begin:"))
(setq n (+ n 1))
(setq rad (nth n list1));(getreal "\n Give the base radius:"))
(setq n (+ n 1))
(setq flag (nth n list1));(getreal "\n Type- 1 for giving top radius and height. 2 for top radius and angle. 3. for height and angle"))
(setq n (+ n 1))
(if (= flag 1)(progn
(setq radtop (nth n list1));(getreal "\n Give the top radius:"))
(setq n (+ n 1))
(setq hc (nth n list1));(getreal "\n Give the height of which Cylinder has to be made:"))
(setq n (+ n 1))
(setq deltar (/ (- radtop rad) hc))
) (progn))
(if (= flag 2)(progn
(setq angle (nth n list1));(getreal "\n Give the angle in degrees:"))
(setq n (+ n 1))
(setq radtop (nth n list1));(getreal "\n Give the top radius:"))
(setq n (+ n 1))
(setq deltar (- (tan angle )))
(setq hc (/ (- radtop rad) deltar))
)(progn))
(if (= flag 3)(progn
(setq angle (nth n list1));(getreal "\n Give the angle in degrees:"))
(setq n (+ n 1))
(setq hc (nth n list1));(getreal "\n Give the height of the cylinder:"))
(setq n (+ n 1))
(setq deltar (- (tan angle )))
(setq radtop (+ (* deltar hc) rad))
)(progn))
(setq z2 (+ hc z1))
(setq radstr (strcat (rtos rad) ""))
(setq deltah (nth n list1));(getreal "\n Give the height differential:"))
(setq n (+ n 1))
(while (<= z1 z2)
(setq ctr (list x1 y1 z1))
(command "circle" ctr radstr)
(setq z1 (+ z1 deltah))
(setq rad (+ rad (* deltar deltah)))
(setq radstr (strcat (rtos rad) ""))
)
(setq height1 (nth n list1));(getreal "\nFont in coordinate units for tag:"))
(setq n (+ n 1))
(setq heightstr (strcat "" (rtos height1) ""))
;(prompt "\nEnter the tag text:")
;(setq tagtext (strcat (read-line) ""))
;(command "text" (list (+ x1 (max rad radtop)) y1 0) heightstr 45.0 tagtext)

)

(defun tan(angle)     ; Function to evaluate the tan value when angle is passed in degree value to it.
(setq angle (* angle pi))
(setq angle (/ angle 180))
(setq ret (/ (sin angle) (cos angle)))
)

(defun menu()         ; Menu Function
(setq filename (open "D:/Text Input/Text Input.txt" "r"))
(setq ab (read-line filename))
(while (/= nil ab)
(setq n 0)
(setq ab (liststaa (sparser ab " ")))
(setq abcd 1)
(if ( = (nth n ab) 1.0)
(progn
(setq abc 1)
(setq n (+ 1 n))
(setq which (nth n ab));(getreal "\n What type of building is required: \n 1.Cone \n 2.Cuboidal  \n 3.Cylindrical \n 4.Any Extruded quadrilateral\n 5.Varying Radius Cylinder. \n Type the number:"))
(setq n (+ n 1))
(if (= which 1) (progn (cone n ab)) (progn))
(if (= which 2) (progn (rect n ab)) (progn))
(if (= which 3) (progn (cyl n ab)) (progn))
(if (= which 4) (progn (quadi n ab)) (progn))
(if (= which 5) (progn (varyradiuscyl n ab)) (progn))
)


(progn
));end of if  internal
(setq ab (read-line filename))
)
)

(defun varyradiuscyl(n list1) ; Function to make Cylinder with varying Radius given different exponential factors, center and intermediate Z coordinate
(setq x1 (nth n list1));(getreal "\n Give the X coordinate of the Center:"))
(setq n (+ n 1))
(setq y1 (nth n list1));(getreal "\n Give the Y coordinate of the Center:"))
(setq n (+ n 1))
(setq z1 (nth n list1));(getreal "\n Give the Z Coordinate from where to begin:"))
(setq n (+ n 1))
(setq z2 (nth n list1));(getreal "\n Give the intermediate Z Coordinate:"))
(setq n (+ n 1))
(setq z3 (nth n list1));(getreal "\n Give the final Z Coordinate:"))
(setq n (+ n 1))
(setq rad (nth n list1));(getreal "\n Give the base radius:"))
(setq n (+ n 1))
(setq alpha1 (nth n list1));(getreal "\n Give the first exponential factor:"))
(setq n (+ n 1))
(setq alpha2 (nth n list1));(getreal "\n Give the second exponential factor:"))
(setq n (+ n 1))
(setq radstr (strcat (rtos rad) ""))
(setq deltah (nth n list1));(getreal "\n Give the height differential:"))
(setq n (+ n 1))
(setq rad1 rad)
(while (< z1 z2)
(setq ctr (list x1 y1 z1))
(command "circle" ctr radstr)
(setq z1 (+ z1 deltah))
(setq rad (* rad (expt alpha1 deltah)))
(setq radstr (strcat (rtos rad) ""))
)
(setq rad2 rad)
(while (< z2 z3)
(setq ctr (list x1 y1 z2))
(command "circle" ctr radstr)
(setq z2 (+ z2 deltah))
(setq rad (* rad (expt alpha2 deltah)))
(setq radstr (strcat (rtos rad) ""))
)
(setq rad3 rad)
   (setq height1 (nth n list1)); (getreal "\nFont in coordinate units for tag:"))
   (setq n (+ n 1))
   (setq heightstr (strcat "" (rtos height1) ""))
   ;(prompt "\nEnter the tag text:")
   ;(setq tagtext (strcat (read-line) ""))
   ;(command "text" (list (+ x1 (max rad1 rad2 rad3) ) y1 0) heightstr 45.0 tagtext)

)

(defun sparser (str delim / ptr lst)
(while (setq ptr (vl-string-search delim str))
(setq lst (cons (substr str 1 ptr) lst))
(setq str (substr str (+ ptr 2)))
)
(reverse (cons str lst))
)





(defun liststaa(strlist)
(setq n1 (length strlist))
(setq intlist nil)
(setq i 0)
(while (< i n1)
(setq intlist (append intlist (list (atof(nth i strlist)))))
(setq i (+ 1 i))
)
(setq a intlist))
